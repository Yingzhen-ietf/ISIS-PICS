module iana-isis-pics {
  yang-version 1.1;
  namespace "urn:ietf:params:xml:ns:yang:iana-isis-pics";
  prefix iana-isis-pics;

  organization
    "IANA";
  contact
    "Internet Assigned Numbers Authority

     Postal: ICANN
             12025 Waterfront Drive, Suite 300
             Los Angeles, CA 90094-2536
             United States of America
     Tel:    +1 310 301 5800
     <mailto:iana@iana.org>";

  description
    "The YANG module defines the identities for IS-IS Protocol
     Implementation Conformance Statement (PICS).

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2025-05-05 {
    description
      "Initial Version";
    reference
      "RFC XXXX: YANG Data Model for IS-IS PICS.";
  }


  identity isis-pics {
    description
      "This identity is used as a base for all ISIS pics defined
       in the 'IS-IS PICS' registry.";
  }

  identity isis-pics-sr-mpls {
    base "isis-pics";
    description
      "The identity for IS-IS PICS support of SR MPLS.";
    reference
      "RFC 8667: IS-IS Extensions for Segment Routing.";
  }
}
