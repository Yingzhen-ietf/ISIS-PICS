module ietf-isis-pics-l2-member-attr {
  yang-version 1.1;
  namespace "urn:ietf:params:xml:ns:yang:ietf-isis-pics-l2-member-attr";
  prefix isis-pics-l2-mem-attr;

  import iana-isis-pics {
    prefix "iana-isis-pics";
  }

  import ietf-isis-pics {
    prefix "isis-pics";
  }

  organization
    "IETF LSR - Link State Routing Working Group";
  contact
    "WG Web:   <http://datatracker.ietf.org/wg/lsr>
     WG List:  <mailto:lsr@ietf.org>

     Author:   Yingzhen Qu
               <mailto:yingzhen.ietf@gmail.com>
     Author:   Les Ginsberg
               <mailto:ginsberg@cisco.com>
     Author:   Tony Przygienda
               <mailto:prz@juniper.net>
     Author:   Bruno Decraene
               <bruno.decraene@orange.com>
     Author:   Yongqing Zhu
               <mailto:zhuyq8@chinatelecom.cn>";

  description
    "The YANG module is used to query an IS-IS Protocol 
     Implementation Conformance Statement (PICS) of Advertising
     Layer 2 Bundle Member Link Attributes in IS-IS (RFC8668).

     This YANG model conforms to the Network Management
     Datastore Architecture (NMDA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  reference
    "RFC XXXX: YANG Data Model for IS-IS Layer 2 Link Attributes
               PICS";

  revision 2025-05-05 {
    description
      "Initial Version";
    reference
      "RFC XXXX: YANG Data Model for IS-IS Layer 2 Link Attributes
                 PICS.";
  }

  container isis-pics-l2-member-attr {
    when "/isis-pics:isis-pics/isis-pics:supported-isis-pics "
       + "= 'iana-isis-pics:isis-pics-l2-member-attr'" {
      description
        "This container only exists when isis-pics-l2-member-attr
         is present in the ietf-isis-pics module.";
    }
    config false;
    description
      "IS-IS Protocol Implementation Conformance Statement (PICS) of
       Advertising Layer 2 Bundle Member Link Attributes.";
    reference
       "RFC 8668: Advertising Layer 2 Bundle Member Link Attributes
                  in IS-IS";


    container l2-bundle-member-attributes-tlv-support {
      presence "Support of L2 bundle member attributes tlv.";
      description
        "Support of L2 bundle member attributes tlv (Type 25)."; 

      leaf-list shared-attribute-sub-tlv-support {
        type uint8;
        description
          "List of sub-tlvs supported for advertising neighbor
           information.";
        reference
          "IANA registry:IS-IS Sub-TLVs for TLVs Advertising Neighbor
           Information. https://www.iana.org/assignments
           /isis-tlv-codepoints/isis-tlv-codepoints.xhtml#
           isis-tlv-codepoints-advertising-neighbor-information";
      }       
    }
  }


  augment "/isis-pics:isis-pics/isis-pics:isis-pics-mptlv" 
  {
    description
      "Augment isis-pics-mptlv container with the tlvs defined
       in RFC 8668.";

    leaf l2-bundle-member-attributes-support {
      type isis-pics:support;
      description
        "MP-TLV support of L2 bundle member attributes tlv (Type 25).";
    }
  }
}
