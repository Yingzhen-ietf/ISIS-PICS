module ietf-isis-pics-mtlv {
  yang-version 1.1;
  namespace "urn:ietf:params:xml:ns:yang:ietf-isis-pics-mtlv";
  prefix isis-pics-mtlv;

  import ietf-isis-pics {
    prefix "isis-pics";
  }

  organization
    "IETF LSR - Link State Routing Working Group";
  contact
    "WG Web:   <http://datatracker.ietf.org/wg/lsr>
     WG List:  <mailto:lsr@ietf.org>

     Author:    Yingzhen Qu
               <mailto:yingzhen.ietf@gmail.com>
     Author:   Les Ginsberg
               <mailto:ginsberg@cisco.com>
     Author:   Tony Przygienda
               <mailto:prz@juniper.net>";

  description
    "ISIS Protocol Implementation Conformance Statement (PICS) is
     defined in ISO 10589. The YANG module is used to query an IS-IS
     implementation of Multi-part TLVs for the conformance of the
     protocol implementation.

     This YANG model conforms to the Network Management
     Datastore Architecture (NMDA) as described in RFC 8342.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-10-01 {
    description
      "Initial Version";
  }

  container isis-pics-mtlv {
    when "/isis-pics:isis-pics/isis-pics:supported-isis-pics "
       + "= 'rfc-mtlv'" {
      description
        "This container only exists when rfc-mtlv is present in
         the ietf-isis-pics module.";
    }
    description
      "IS-IS Protocol Implementation Conformance Statement (PICS)
       for RFC xxxx: Multi-part TLVs in IS-IS";


    container mp-top-tlv-support {
      description
        "Support of MP-TLV for isis top-level tlvs.";

      leaf inst-id-support {
        type boolean;
        default false;
        description
          "MP-TLV support of Instance Identifier TLV(type 7).";
      }
      leaf extended-is-reachability-support {
        type boolean;
        default false;
        description
          "MP-TLV support of Extended IS Reachability TLV(type 22).";
      }
      leaf is-nbr-attr-support {
        type boolean;
        default false;
        description
          "MP-TLV support of IS Neighbor Attribute TLV(type 23).";
      }
      leaf l2-bundle-mbr-support {
        type boolean;
        default false;
        description
          "MP-TLV support of L2 Bundle Member Attributes TLV(type 25).";
      }
      leaf srv6-locator-support {
        type boolean;
        default false;
        description
          "MP-TLV support of SRv6 Locator TLV(type 27).";
      }
      leaf extended-ip-reachability-support {
        type boolean;
        default false;
        description
          "MP-TLV support of Extended IP Reachability TLV(type 135).";
      }
      leaf gmpls-srlb-support {
        type boolean;
        default false;
        description
          "MP-TLV support of GMPLS-SRLG TLV(type 138).";
      }
      leaf inter-as-reachability-support {
        type boolean;
        default false;
        description
          "MP-TLV support of inter-AS reachability information TLV
           (type 141).";
      }
      leaf gaadr-tlv-support {
        type boolean;
        default false;
        description
          "MP-TLV Group Address TLV(type 142).";
      }
      leaf mt-port-cap-support {
        type boolean;
        default false;
        description
          "MP-TLV support of MT-Port-Cap TLV(type 143).";
      }
      leaf mt-capability-support {
        type boolean;
        default false;
        description
          "MP-TLV support of MT-Capability TLV(type 144).";
      }
      leaf mac-ri-support {
        type boolean;
        default false;
        description
          "MP-TLV support of MAC-RI TLV(type 147).";
      }
      leaf bfd-enabled-support {
        type boolean;
        default false;
        description
          "MP-TLV support of BFD-Enabled TLV(type 148).";
      }
      leaf sid-label-binding-support {
        type boolean;
        default false;
        description
          "MP-TLV support of Segment Identifier/Label Binding TLV
          (type 149).";
      }
      leaf mt-sid-label-binding-support {
        type boolean;
        default false;
        description
          "MP-TLV support of Multi-Topology Segment Identifier/Label
          Binding TLV(type 150).";
      }
      leaf mt-isn-support {
        type boolean;
        default false;
        description
          "MP-TLV support of MT-ISN TLV(type 222).";
      }
      leaf mt-is-nbr-attr-support {
        type boolean;
        default false;
        description
          "MP-TLV support of MT IS Neighbor Attribute TLV(type 223).";
      }
      leaf mt-ip-reach-support {
        type boolean;
        default false;
        description
          "MP-TLV support of MT IP Reachable TLV(type 235).";
      }
      leaf ipv6-ip-reach-support {
        type boolean;
        default false;
        description
          "MP-TLV support of IPv6 IP Reach TLV(type 236).";
      }
      leaf mt-ipv6-ip-support {
        type boolean;
        default false;
        description
          "MP-TLV support of MT IPv6 IP Reach TLV(type 237).";
      }
      leaf app-specific-srlg-support {
        type boolean;
        default false;
        description
          "MP-TLV support of Application-Specific SRLG TLV(type 238).";
      }
      leaf router-capability-support {
        type boolean;
        default false;
        description
          "MP-TLV support of IS-IS Router Capability TLV(type 242).";
      }
      leaf generic-info-support {
        type boolean;
        default false;
        description
          "MP-TLV support of Generic Information TLV(type 251).";
      }
    }

    container mp-sub-tlv-nbr-info-support {
      description
        "Support of MP-TLV for IS-IS sub-tlvs for advertising
         neighbor information.";
      leaf link-msd-support {
        type boolean;
        default false;
        description
          "MP-TLV support of Link MSD Sub-TLV(type 15).";
      }
      leaf app-spec-link-attr-support {
        type boolean;
        default false;
        description
          "MP-TLV support of Application-Specific Link Attributes 
          Sub-TLV(type 16).";
      }
      leaf generic-metric-support {
        type boolean;
        default false;
        description
          "MP-TLV support of Generic Metric Sub-TLV(type 17).";
      }
      leaf int-switch-capability-support {
        type boolean;
        default false;
        description
          "MP-TLV support of Interface Switching Capability Descriptor
           Sub-TLV(type 21).";
      }
      leaf iacd-support {
        type boolean;
        default false;
        description
          "MP-TLV support of Interface Adjustment Capability Descriptor
           Sub-TLV(type 27).";
      }
      leaf spb-a-oalg-support {
        type boolean;
        default false;
        description
          "MP-TLV support of SPB-A-OALG Sub-TLV(type 30).";
      }
      leaf l2-bundle-adj-sid-support {
        type boolean;
        default false;
        description
          "MP-TLV support of L2 Bundle Member Adj-SID Sub-TLV
           (type 41).";
      }
      leaf l2-bundle-lan-adj-sid-support {
        type boolean;
        default false;
        description
          "MP-TLV support of L2 Bundle Member LAN Adj-SID Sub-TLV
           (type 42).";
      }
      leaf srv6-endx-sid-support {
        type boolean;
        default false;
        description
          "MP-TLV support of SRv6 Eend.X SID Sub-TLV(type 43).";
      }
      leaf srv6-lan-endx-sid-support {
        type boolean;
        default false;
        description
          "MP-TLV support of SRv6 LAN End.X SID Sub-TLV(type 44).";
      }
    }

    container mp-sub-tlv-prefix-reachability-support {
      description
        "Support of MP-TLV for IS-IS sub-tlvs for advertising
         prefix reachability.";
      leaf srv6-end-sid-support {
        type boolean;
        default false;
        description
          "MP-TLV support of SRv6 End SID Sub-TLV(type 5).";
      }
      leaf bier-info-support {
        type boolean;
        default false;
        description
          "MP-TLV support of BIER Info Sub-TLV(type 32).";
      }
    }

    container mp-sub-tlv-mt-capability-support {
      description
        "Support of MP-TLV for IS-IS sub-tlvs for MT-Capability.";
      leaf spb-i-oalg-support {
        type boolean;
        default false;
        description
          "MP-TLV support of SPB-I-OALG Sub-TLV(type 2).";
      }
      leaf spbm-si-support {
        type boolean;
        default false;
        description
          "MP-TLV support of SPBM-SI Sub-TLV(type 3).";
      }
      leaf spbv-addr-support {
        type boolean;
        default false;
        description
          "MP-TLV support of SPBV-ADDR Sub-TLV(type 4).";
      }
      leaf nickname-support {
        type boolean;
        default false;
        description
          "MP-TLV support of NICKNAME Sub-TLV(type 6).";
      }
      leaf tree-rt-id-support {
        type boolean;
        default false;
        description
          "MP-TLV support of TREE-RT-IDs Sub-TLV(type 8).";
      }
      leaf tree-use-id-support {
        type boolean;
        default false;
        description
          "MP-TLV support of TREE-USE-IDs Sub-TLV(type 9).";
      }
      leaf int-vlan-support {
        type boolean;
        default false;
        description
          "MP-TLV support of INT-VLAN Sub-TLV(type 10).";
      }
      leaf vlan-group-support {
        type boolean;
        default false;
        description
          "MP-TLV support of VLAN-GROUP Sub-TLV(type 14).";
      }
      leaf int-label-support {
        type boolean;
        default false;
        description
          "MP-TLV support of SPBM-SI Sub-TLV(type 15).";
      }
      leaf rbchannels-support {
        type boolean;
        default false;
        description
          "MP-TLV support of RBCHANNELS Sub-TLV(type 16).";
      }
      leaf affinity-support {
        type boolean;
        default false;
        description
          "MP-TLV support of AFFINITY Sub-TLV(type 17).";
      }
      leaf label-group-support {
        type boolean;
        default false;
        description
          "MP-TLV support of LABEL-GROUP Sub-TLV(type 18).";
      }
      leaf topo-support {
        type boolean;
        default false;
        description
          "MP-TLV support of TOpology Sub-TLV(type 21).";
      }
    }

    container mp-sub-tlv-router-capability-support {
      description
        "Support of MP-TLV for IS-IS sub-tlvs for IS-IS
         Router Capability.";
      leaf te-mesh-ipv4-support {
        type boolean;
        default false;
        description
          "MP-TLV support of TE-MESH_GROUP IPv4 Sub-TLV(type 3).";
      }
      leaf te-mesh-ip6-support {
        type boolean;
        default false;
        description
          "MP-TLV support of TE-MESH-GROUP IPv6 Sub-TLV(type 4).";
      }
      leaf nickname-support {
        type boolean;
        default false;
        description
          "MP-TLV support of NICKNAME Sub-TLV(type 6).";
      }
      leaf tree-rt-id-support {
        type boolean;
        default false;
        description
          "MP-TLV support of TREE-RT-IDs Sub-TLV(type 8).";
      }
      leaf tree-use-id-support {
        type boolean;
        default false;
        description
          "MP-TLV support of TREE-USE-IDs Sub-TLV(type 9).";
      }
      leaf int-vlan-support {
        type boolean;
        default false;
        description
          "MP-TLV support of INT-VLAN Sub-TLV(type 10).";
      }
      leaf vlan-group-support {
        type boolean;
        default false;
        description
          "MP-TLV support of VLAN-GROUP Sub-TLV(type 14).";
      }
      leaf int-label-support {
        type boolean;
        default false;
        description
          "MP-TLV support of SPBM-SI Sub-TLV(type 15).";
      }
      leaf rbchannels-support {
        type boolean;
        default false;
        description
          "MP-TLV support of RBCHANNELS Sub-TLV(type 16).";
      }
      leaf affinity-support {
        type boolean;
        default false;
        description
          "MP-TLV support of AFFINITY Sub-TLV(type 17).";
      }
      leaf label-group-support {
        type boolean;
        default false;
        description
          "MP-TLV support of LABEL-GROUP Sub-TLV(type 18).";
      }
      leaf node-msd-support {
        type boolean;
        default false;
        description
          "MP-TLV support of Node MSD Sub-TLV(type 23).";
      }
      leaf flood-reflect-support {
        type boolean;
        default false;
        description
          "MP-TLV support of Flood Reflection Discovery Sub-TLV
          (type 161).";
      }
    }

    container mp-sub-sub-tlv-app-specific-link-attr-support {
      description
        "Support of MP-TLV for IS-IS sub-sub-tlvs for Application
         Specific Link Attributes.";
      leaf generic-metric-support {
        type boolean;
        default false;
        description
          "MP-TLV support of Generic Metric sub-sub-TLV(type 17).";
      }
    }   
  }  
}
